module ietf-l3vpn-ntw-sg {
  yang-version 1.1;
  namespace "urn:ietf:params:xml:ns:yang:ietf-l3vpn-ntw-sg";
  prefix l3vpn-ntw-sg;

  import ietf-vpn-common {
    prefix vpn-common;
    reference
     "RFC XXXX: A Layer 3 VPN Network YANG Model.";
  }

  import ietf-inet-types {
    prefix inet;
    reference
      "Section 4 of RFC 6991";
  }

  import ietf-yang-types {
    prefix yang;
    reference
      "Section 3 of RFC 6991";
  }

  import ietf-packet-fields {
    prefix packet-fields;
    reference
      "RFC 8519: YANG Data Model for Network Access
                 Control Lists (ACLs)";
  }

  organization
    "IETF OPSA (Operations and Management Area) Working Group ";
  contact
    "WG Web:   <http://tools.ietf.org/wg/opsawg/>
        WG List:  <mailto:opsawg@ietf.org>
        Author:    Samier Barguil
                  <mailto:samier.barguilgiraldo.ext@telefonica.com>
        Editor:    Oscar Gonzalez de Dios
                  <mailto:oscar.gonzalezdedios@telefonica.com>
        Author:   Mohamed Boucadair
                  <mailto:mohamed.boucadair@orange.com>           
        Author:    Luis Angel Munoz
                  <mailto:luis-angel.munoz@vodafone.com>
        Author:    Alejandro Aguado
                  <mailto:alejandro.aguado_martin@nokia.com> 
    ";
  description
    "This YANG module defines a generic network-oriented model
     for the configuration of Layer 3 Virtual Private Networks.
     Copyright (c) 2020 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2020-06-16 {
    description
      "Initial revision.";
    reference
      "RFC XXXX: A Layer 3 VPN Network YANG Model";
      // RFC Ed.: replace XXXX with actual RFC number and remove
     // this note
  }

  /* Features */

  feature msdp {
    description
      "This feature indicates that msdp capabilities
       are supported by the VPN.";
  }

  feature input-bw {
    description
      "This feature indicates the support of
       the 'input-bw' limit.";
  }

  /* Typedefs */


  /* Identities */

  identity eth-inf-type {
    description
      "Identity of the Ethernet interface type.";
  }

  identity tagged {
    base eth-inf-type;
    description
      "Identity of the tagged interface type.";
  }

  identity untagged {
    base eth-inf-type;
    description
      "Identity of the untagged interface type.";
  }

  identity lag {
    base eth-inf-type;
    description
      "Identity of the LAG interface type.";
  }

  identity bearer-inf-type {
    description
      "Identity for the bearer interface type.";
  }

  identity port-id {
    base bearer-inf-type;
    description
      "Identity for the priority-tagged interface.";
  }

  identity lag-id {
    base bearer-inf-type;
    description
      "Identity for the priority-tagged interface.";
  }

  
  identity vxlan-peer-mode {
    description
      "Base identity for the VXLAN peer mode.";
  }

  identity static-mode {
    base vxlan-peer-mode;
    description
      "Identity for VXLAN access in the static mode.";
  }

  identity bgp-mode {
    base vxlan-peer-mode;
    description
      "Identity for VXLAN access using BGP EVPN.";
  }

  identity bw-direction {
    description
      "Identity for the bandwidth direction.";
  }

  identity input-bw {
    base bw-direction;
    description
      "Identity for the input bandwidth.";
  }

  identity output-bw {
    base bw-direction;
    description
      "Identity for the output bandwidth.";
  }

  identity bw-type {
    description
      "Identity of the bandwidth type.";
  }

  identity bw-per-cos {
    base bw-type;
    description
      "Bandwidth is per CoS.";
  }

  identity bw-per-port {
    base bw-type;
    description
      "Bandwidth is per site network access.";
  }

  identity bw-per-site {
    base bw-type;
    description
      "Bandwidth is per site.  It is applicable to
       all the site network accesses within a site.";
  }

  identity bw-per-svc {
    base bw-type;
    description
      "Bandwidth is per VPN service.";
  }

  /* Groupings */

  grouping security-params {
    container security {
      leaf auth-key {
        type string;
        description
          "MD5 authentication password for the connection towards the
           customer edge.";
      }
      description
        "Container for aggregating any security parameter for routing
         sessions between a PE and a CE.";
    }
    description
      "Grouping to define security parameters";
  }

  grouping ports {
    choice source-port {
      container source-port-range-or-operator {
        uses packet-fields:port-range-or-operator;
        description
          "Source port definition.";
      }
      description
        "Choice of specifying the source port or referring to
         a group of source port numbers.";
    }
    choice destination-port {
      container destination-port-range-or-operator {
        uses packet-fields:port-range-or-operator;
        description
          "Destination port definition.";
      }
      description
        "Choice of specifying a destination port or referring
         to a group of destination port numbers.";
    }
    description
      "Choice of specifying a source or destination port numbers.";
  }

  /* Main Blocks */

  /* Main l3vpn-ntw */
  container l3vpn-ntw {
    container vpn-profiles {
      uses vpn-common:vpn-profile-cfg;
      description
        "Contains the valid VPN Profiles to reference 
        in the VPN service.";
    }
    container vpn-services {
      list vpn-service {
        key "vpn-id";
        uses vpn-common:service-status;
        
        leaf vpn-id {
            type vpn-common:svc-id;
            description
              "VPN identifier.
          This identifier has a local meaning.";                       
          }
          
        leaf vpn-type {
            type identityref {
              base vpn-common:vpn-signaling-type;
              }
            description
              "Service type";
          }    
          
        leaf l3sm-vpn-id {
            type vpn-common:svc-id;
            description
              "Pointer to the L3SM service.";
          }

        leaf customer-name {
            type string;
            description
              "Name of the customer that actually uses the VPN service.";
          }
        
        leaf vpn-service-topology {
            type identityref {
              base vpn-common:vpn-topology;
            }
            default "vpn-common:any-to-any";
            description
              "VPN service topology.";
          }
        
        leaf description {
            type string;
            description
              "Textual description of a VPN service.";
          }
        container ie-profiles {
            list ie-profile {
              key "ie-profile-id";
              leaf ie-profile-id {
                type string;
                description
                  "IE profile id.";
              }
              uses vpn-common:rt-rd;
              description
                "List for Imort/Export profile.";
            }
            description
              "Container for Import/Export profiles.";
          }

       uses vpn-common:svc-transport-encapsulation;

          container vpn-nodes {
            description
              "Container for VPN nodes.";
                list vpn-node {
                  key "ne-id";
                  
                  leaf vpn-node-id {
                    type union {
                      type vpn-common:svc-id;
                      type uint32;
                    }
                    description
                      "Type STRING or NUMBER Serivice-Id";
                  }
                  
                  leaf local-autonomous-system {
                    type inet:as-number;
                    description
                      "Provider AS number in case the customer
                       requests BGP routing.";
                  }
                  
                  leaf description {
                    type string;
                    description
                      "Textual description of the VPN node.";
                  }
                  
                  leaf ne-id {
                    type string;
                    description
                      "Unique identifier of the network element
                        where the vpn-node is deployed.";
                  }
                  
                  leaf router-id {
                    type inet:ip-address;
                    description
                      "router-id information can be ipv4/6 
                      addresses";
                  }

                  leaf address-family {
                    type vpn-common:address-family;
                    description
                      "Address family used for router-id information.";
                  }
                  
                  leaf node-role {
                    type identityref {
                      base vpn-common:site-role;
                    }
                    default "vpn-common:any-to-any-role";
                    description
                      "Role of the vpn-node in the IP VPN.";
                  }
                  uses vpn-common:rt-rd;
                  uses vpn-common:service-status;

                  leaf node-ie-profile {
                       type leafref {
                         path "/l3vpn-ntw/vpn-services/"
                          + "vpn-service/ie-profiles/ie-profile/ie-profile-id";
                        }
                     description
                       "node Import/Export profile.";
                  }
                  
                  container vpn-network-accesses {
                    list vpn-network-access {
                      key "id";
                      leaf id {
                        type vpn-common:svc-id;
                        description
                          "Identifier for the access.";
                      }
                      leaf port-id {
                        type vpn-common:svc-id;
                        description
                          "Identifier for the network access.";
                      }
                      leaf description {
                        type string;
                        description
                          "Textual description of a VPN service.";
                      }
                      

                      uses vpn-common:service-status;
                      leaf vpn-network-access-type {
                        type identityref {
                          base vpn-common:site-network-access-type;
                        }
                        default "vpn-common:point-to-point";
                        description
                          "Describes the type of connection, e.g.,
                           point-to-point or multipoint.";
                      }
                      
                    container connection {
                      leaf encapsulation-type {
                        type identityref {
                          base vpn-common:encapsulation-type;
                        }
                        default "vpn-common:untagged-int";
                        description
                          "Encapsulation type.  By default, the
                           encapsulation type is set to 'untagged'.";
                      }

                      container logical-interface {
                        leaf peer-reference {
                          type uint32;
                          description
                            "Specify the associated logical peer
                             interface";
                        }
                        description
                          "Reference of a logical interface type.";
                      }

                      container tagged-interface {
                        leaf type {
                          type identityref {
                            base vpn-common:encapsulation-type;
                          }
                          default "vpn-common:priority-tagged";
                          description
                            "Tagged interface type.  By default,
                             the type of the tagged interface is
                             'priority-tagged'.";
                        }

                        container dot1q-vlan-tagged {
                          when "derived-from-or-self(../type, "
                             + "'vpn-common:dot1q')" {
                            description
                              "Only applies when the type of the tagged
                               interface is 'dot1q'.";
                          }
                          if-feature "vpn-common:dot1q";
                          leaf tag-type {
                            type identityref {
                              base vpn-common:tag-type;
                            }
                            default "vpn-common:c-vlan";
                            description
                              "Tag type.  By default, the tag type is
                               'c-vlan'.";
                          }
                          leaf cvlan-id {
                            type uint16;
                            description
                              "VLAN identifier.";
                          }
                          description
                            "Tagged interface.";
                        }
                        container priority-tagged {
                          when "derived-from-or-self(../type, "
                             + "'vpn-common:priority-tagged')" {
                            description
                              "Only applies when the type of the tagged
                               interface is 'priority-tagged'.";
                          }
                          leaf tag-type {
                            type identityref {
                              base vpn-common:tag-type;
                            }
                            default "vpn-common:c-vlan";
                            description
                              "Tag type.  By default, the tag type is
                               'c-vlan'.";
                          }
                          description
                            "Priority tagged.";
                        }
                        container qinq {
                          when "derived-from-or-self(../type, "
                             + "'vpn-common:qinq')" {
                            description
                              "Only applies when the type of the tagged
                               interface is 'qinq'.";
                          }
                          if-feature "vpn-common:qinq";
                          leaf tag-type {
                            type identityref {
                              base vpn-common:tag-type;
                            }
                            default "vpn-common:c-s-vlan";
                            description
                              "Tag type.  By default, the tag type is
                               'c-s-vlan'.";
                          }
                          leaf svlan-id {
                            type uint16;
                            mandatory true;
                            description
                              "SVLAN identifier.";
                          }
                          leaf cvlan-id {
                            type uint16;
                            mandatory true;
                            description
                              "CVLAN identifier.";
                          }
                          description
                            "QinQ.";
                        }
                        container qinany {
                          when "derived-from-or-self(../type, "
                             + "'vpn-common:qinany')" {
                            description
                              "Only applies when the type of the tagged
                               interface is 'qinany'.";
                          }
                          if-feature "vpn-common:qinany";
                          leaf tag-type {
                            type identityref {
                              base vpn-common:tag-type;
                            }
                            default "vpn-common:s-vlan";
                            description
                              "Tag type.  By default, the tag type is
                               's-vlan'.";
                          }
                          leaf svlan-id {
                            type uint16;
                            mandatory true;
                            description
                              "Service VLAN ID.";
                          }
                          description
                            "Container for QinAny.";
                        }
                        container vxlan {
                          when "derived-from-or-self(../type, "
                             + "'vpn-common:vxlan')" {
                            description
                              "Only applies when the type of the tagged
                               interface is 'vxlan'.";
                          }
                          if-feature "vpn-common:vxlan";
                          leaf vni-id {
                            type uint32;
                            mandatory true;
                            description
                              "VXLAN Network Identifier (VNI).";
                          }
                          leaf peer-mode {
                            type identityref {
                              base vxlan-peer-mode;
                            }
                            default "static-mode";
                            description
                              "Specifies the VXLAN access mode.  By default,
                               the peer mode is set to 'static-mode'.";
                          }
                          list peer-list {
                            key "peer-ip";
                            leaf peer-ip {
                              type inet:ip-address;
                              description
                                "Peer IP.";
                            }
                            description
                              "List of peer IP addresses.";
                          }
                          description
                            "QinQ.";
                        }
                        description
                          "Container for tagged interfaces.";
                      }
                      container bearer {
                        leaf bearer-reference {
                          if-feature "vpn-common:bearer-reference";
                          type string;
                          description
                            "This is an internal reference for the SP.";
                        }
                        
                        container pseudowire {
                            leaf vcid {
                              type uint32;
                              description
                                "PW or VC identifier.";
                            }
                            leaf far-end {
                              type union {
                                type uint32;
                                type inet:ipv4-address;
                              }
                              description
                                "SDP/Far End/LDP Neighbour reference.";
                            }
                            description
                              "Pseudowire termination parameters";
                          }
                          container vpls {
                            leaf vcid {
                              type union {
                                type uint32;
                                type string;
                              }
                              description
                                "VCID identifier,IRB/RVPPLs interface
                                 supported using string
                                 format.";
                            }
                            leaf far-end {
                              type union {
                                type uint32;
                                type inet:ipv4-address;
                              }
                              description
                                "SDP/Far End/LDP Neighbour reference.";
                            }
                            description
                              "Pseudowire termination parameters";
                          }

                        description
                          "Defines physical properties of a site attachment.";
                      }
                      description
                        "Encapsulation types";
                    }

                    container ip-connection {
                      container ipv4 {
                        if-feature "vpn-common:ipv4";
                        leaf address-allocation-type {
                          type identityref {
                            base vpn-common:address-allocation-type;
                          }
                          must "not(derived-from-or-self(current(), 'vpn-common:slaac')"
                             + " or derived-from-or-self(current(), "
                             + "'vpn-common:provider-dhcp-slaac'))" {
                            error-message "SLAAC is only applicable to IPv6";
                          }
                          description
                            "Defines how addresses are allocated.
                             If there is no value for the address
                             allocation type, then IPv4 is not enabled.";
                        }
                        container provider-dhcp {
                          when "derived-from-or-self(../address-allocation-type, "
                             + "'vpn-common:provider-dhcp')" {
                            description
                              "Only applies when addresses are allocated by DHCP.";
                          }
                          leaf provider-address {
                            type inet:ipv4-address;
                            description
                              "Address of provider side.  If provider-address is not
                               specified, then prefix length should not be specified
                               either.  It also implies provider-dhcp allocation is
                               not enabled.  If provider-address is specified, then
                               the prefix length may or may not be specified.";
                          }
                          leaf prefix-length {
                            type uint8 {
                              range "0..32";
                            }
                            must '(../provider-address)' {
                              error-message
                                "If the prefix length is specified, provider-address
                                 must also be specified.";
                              description
                                "If the prefix length is specified, provider-address
                                 must also be specified.";
                            }
                            description
                              "Subnet prefix length expressed in bits.
                               If not specified, or specified as zero,
                               this means the customer leaves the actual
                               prefix length value to the provider.";
                          }
                          choice address-assign {
                            default "number";
                            case number {
                              leaf number-of-dynamic-address {
                                type uint16;
                                default "1";
                                description
                                  "Describes the number of IP addresses
                                   the customer requires.";
                              }
                            }
                            case explicit {
                              container customer-addresses {
                                list address-group {
                                  key "group-id";
                                  leaf group-id {
                                    type string;
                                    description
                                      "Group-id for the address range from
                                       start-address to end-address.";
                                  }
                                  leaf start-address {
                                    type inet:ipv4-address;
                                    description
                                      "First address.";
                                  }
                                  leaf end-address {
                                    type inet:ipv4-address;
                                    description
                                      "Last address.";
                                  }
                                  description
                                    "Describes IP addresses allocated by DHCP.
                                     When only start-address or only end-address
                                     is present, it represents a single address.
                                     When both start-address and end-address are
                                     specified, it implies a range inclusive of both
                                     addresses.  If no address is specified, it implies
                                     customer addresses group is not supported.";
                                }
                                description
                                  "Container for customer addresses is allocated by 
                                   DHCP.";
                              }
                            }
                            description
                              "Choice for the way to assign addresses.";
                          }
                          description
                            "DHCP allocated addresses related parameters.";
                        }
                        container dhcp-relay {
                          when "derived-from-or-self(../address-allocation-type, "
                             + "'vpn-common:provider-dhcp-relay')" {
                            description
                              "Only applies when provider is required to implement
                               DHCP relay function.";
                          }
                          leaf provider-address {
                            type inet:ipv4-address;
                            description
                              "Address of provider side.  If provider-address is not
                               specified, then prefix length should not be specified
                               either.  It also implies provider-dhcp allocation is
                               not enabled.  If provider-address is specified, then
                               prefix length may or may not be specified.";
                          }
                          leaf prefix-length {
                            type uint8 {
                              range "0..32";
                            }
                            must '(../provider-address)' {
                              error-message
                                "If prefix length is specified, provider-address
                                 must also be specified.";
                              description
                                "If prefix length is specified, provider-address
                                 must also be specified.";
                            }
                            description
                              "Subnet prefix length expressed in bits.  If not
                               specified, or specified as zero, this means the
                               customer leaves the actual prefix length value
                               to the provider.";
                          }
                          container customer-dhcp-servers {
                            leaf-list server-ip-address {
                              type inet:ipv4-address;
                              description
                                "IP address of customer DHCP server.";
                            }
                            description
                              "Container for list of customer DHCP servers.";
                          }
                          description
                            "DHCP relay provided by operator.";
                        }
                        container static-addresses {
                          when "derived-from-or-self(../address-allocation-type, "
                             + "'vpn-common:static-address')" {
                            description
                              "Only applies when protocol allocation type is static.";
                          }
                          leaf primary-address {
                            type leafref {
                              path "/l3vpn-ntw/vpn-services/vpn-service/vpn-nodes/"
                                 + "vpn-node/vpn-network-accesses/vpn-network-access/"
                                 + "ip-connection/ipv4/static-addresses/address/" 
                                 + "address-id";
                            }
                            description
                              "Principal address of the connection.";
                          }
                          list address {
                            key "address-id";
                            leaf address-id {
                              type string;
                              description
                                "IPv4 Address";
                            }
                            leaf provider-address {
                              type inet:ipv4-address;
                              description
                                "IPv4 Address List of the provider side.
                                 When the protocol allocation type is static,
                                 the provider address must be configured.";
                            }
                            leaf customer-address {
                              type inet:ipv4-address;
                              description
                                "IPv4 Address of customer side.";
                            }
                            leaf prefix-length {
                              type uint8 {
                                range "0..32";
                              }
                              description
                                "Subnet prefix length expressed in bits.
                                 It is applied to both provider-address
                                 and customer-address.";
                            }
                            description
                              "Describes IPv4 addresses used.";
                          }
                          description
                            "Describes IPv4 addresses used.";
                        }
                        description
                          "IPv4-specific parameters.";
                      }
                      container ipv6 {
                        if-feature "vpn-common:ipv6";
                        leaf address-allocation-type {
                          type identityref {
                            base vpn-common:address-allocation-type;
                          }
                          description
                            "Defines how addresses are allocated.
                             If there is no value for the address
                             allocation type, then IPv6 is
                             not enabled.";
                        }
                        container provider-dhcp {
                          when "derived-from-or-self(../address-allocation-type, "
                             + "'vpn-common:provider-dhcp') "
                             + "or derived-from-or-self(../address-allocation-type, "
                             + "'vpn-common:provider-dhcp-slaac')" {
                            description
                              "Only applies when addresses are allocated by DHCP.";
                          }
                          leaf provider-address {
                            type inet:ipv6-address;
                            description
                              "Address of the provider side.  If provider-address
                               is not specified, then prefix length should not be
                               specified either.  It also implies provider-dhcp
                               allocation is not enabled.  If provider-address is
                               specified, then prefix length may or may
                               not be specified.";
                          }
                          leaf prefix-length {
                            type uint8 {
                              range "0..128";
                            }
                            must '(../provider-address)' {
                              error-message
                                "If prefix length is specified, provider-address
                                 must also be specified.";
                              description
                                "If prefix length is specified, provider-address
                                 must also be specified.";
                            }
                            description
                              "Subnet prefix length expressed in bits.  If not
                               specified, or specified as zero, this means the
                               customer leaves the actual prefix length value
                               to the provider.";
                          }
                          choice address-assign {
                            default "number";
                            case number {
                              leaf number-of-dynamic-address {
                                type uint16;
                                default "1";
                                description
                                  "Describes the number of IP addresses the customer
                                   requires.";
                              }
                            }
                            case explicit {
                              container customer-addresses {
                                list address-group {
                                  key "group-id";
                                  leaf group-id {
                                    type string;
                                    description
                                      "Group-id for the address range from
                                       start-address to end-address.";
                                  }
                                  leaf start-address {
                                    type inet:ipv6-address;
                                    description
                                      "First address.";
                                  }
                                  leaf end-address {
                                    type inet:ipv6-address;
                                    description
                                      "Last address.";
                                  }
                                  description
                                    "Describes IP addresses allocated by DHCP.
                                     When only start-address or only end-address
                                     is present, it represents a single address.
                                     When both start-addressand end-address are
                                     specified, it implies a range
                                     inclusive of both addresses.
                                     If no address is specified, it implies
                                     customer addresses group is
                                     not supported.";
                                }
                                description
                                  "Container for customer addresses allocated 
                                   by DHCP.";
                              }
                            }
                            description
                              "Choice for the way to assign addresses.";
                          }
                          description
                            "DHCP allocated addresses related parameters.";
                        }
                        container dhcp-relay {
                          when "derived-from-or-self(../address-allocation-type, "
                             + "'vpn-common:provider-dhcp-relay')" {
                            description
                              "Only applies when the provider is required
                               to implement DHCP relay function.";
                          }
                          leaf provider-address {
                            type inet:ipv6-address;
                            description
                              "Address of the provider side.  If provider-address
                               is not specified, then prefix length should not be
                               specified either.  It also implies provider-dhcp
                               allocation is not enabled.  If provider address
                               is specified, then prefix length may or may
                               not be specified.";
                          }
                          leaf prefix-length {
                            type uint8 {
                              range "0..128";
                            }
                            must '(../provider-address)' {
                              error-message
                                "If prefix length is specified, provider-address
                                 must also be specified.";
                              description
                                "If prefix length is specified, provider-address
                                 must also be specified.";
                            }
                            description
                              "Subnet prefix length expressed in bits.  If not
                               specified, or specified as zero, this means the
                               customer leaves the actual prefix length value
                               to the provider.";
                          }
                          container customer-dhcp-servers {
                            leaf-list server-ip-address {
                              type inet:ipv6-address;
                              description
                                "This node contains the IP address of
                                 the customer DHCP server.  If the DHCP relay
                                 function is implemented by the
                                 provider, this node contains the
                                 configured value.";
                            }
                            description
                              "Container for list of customer DHCP servers.";
                          }
                          description
                            "DHCP relay provided by operator.";
                        }
                        container static-addresses {
                          when "derived-from-or-self(../address-allocation-type, "
                             + "'vpn-common:static-address')" {
                            description
                              "Only applies when protocol allocation type is static.";
                          }
                          leaf primary-address {
                            type leafref {
                              path "/l3vpn-ntw/vpn-services/vpn-service/vpn-nodes/"
                                 + "vpn-node/vpn-network-accesses/vpn-network-access/"
                                 + "ip-connection/ipv6/static-addresses/address/" 
                                 + "address-id";
                            }
                            description
                              "Principal address of the connection";
                          }
                          list address {
                            key "address-id";
                            leaf address-id {
                              type string;
                              description
                                "IPv4 Address";
                            }
                            leaf provider-address {
                              type inet:ipv6-address;
                              description
                                "IPv6 Address of the provider side.  When the protocol
                                 allocation type is static, the provider address
                                 must be configured.";
                            }
                            leaf customer-address {
                              type inet:ipv6-address;
                              description
                                "The IPv6 Address of the customer side.";
                            }
                            leaf prefix-length {
                              type uint8 {
                                range "0..128";
                              }
                              description
                                "Subnet prefix length expressed in bits.
                                 It is applied to both provider-address and
                                 customer-address.";
                            }
                            description
                              "Describes IPv6 addresses used.";
                          }
                          description
                            "IPv6-specific parameters.";
                        }
                        description
                          "IPv6-specific parameters.";
                      }
                      container oam {
                        container bfd {
                          if-feature "vpn-common:bfd";
                          leaf enabled {
                            type boolean;
                            default "false";
                            description
                              "If true, BFD activation is required.";
                          }
                          choice holdtime {
                            default "fixed";
                            case fixed {
                              leaf fixed-value {
                                type uint32;
                                units "msec";
                                description
                                  "Expected BFD holdtime expressed in msec.  The customer
                                   may impose some fixed values for the holdtime period
                                   if the provider allows the customer use this function.
                                   If the provider doesn't allow the customer to use this
                                   function, the fixed-value will not be set.";
                              }
                            }
                            case profile {
                              leaf profile-name {
                                type leafref {
                                  path "/l3vpn-ntw/vpn-profiles/valid-provider-identifiers/"
                                     + "bfd-profile-identifier/id";
                                }
                                description
                                  "Well-known SP profile name.  The provider can propose
                                   some profiles to the customer, depending on the service
                                   level the customer wants to achieve.  Profile names
                                   must be communicated to the customer.";
                              }
                              description
                                "Well-known SP profile.";
                            }
                            description
                              "Choice for holdtime flavor.";
                          }
                          description
                            "Container for BFD.";
                        }
                        description
                          "Defines the Operations, Administration, and Maintenance (OAM)
                           mechanisms used on the connection.  BFD is set as a fault
                           detection mechanism, but the 'oam' container can easily
                           be augmented by other mechanisms";
                      }
                      description
                        "Defines connection parameters.";
                    }
                          container security {
                              container encryption {
                                  if-feature "vpn-common:encryption";
                                  
                                  leaf enabled {
                                    type boolean;
                                    default "false";
                                    description
                                      "If true, traffic encryption on the connection
                                       is required. It is disabled, otherwise.";
                                  }
                                  
                                  leaf layer {
                                    when "../enabled = 'true'" {
                                      description
                                        "Require a value for layer when enabled 
                                         is true.";
                                    }
                                    type enumeration {
                                      enum layer2 {
                                        description
                                          "Encryption will occur at Layer 2.";
                                      }
                                      enum layer3 {
                                        description
                                          "Encryption will occur at Layer 3.
                                           For example, IPsec may be used when
                                           a customer requests Layer 3 encryption.";
                                      }
                                    }
                                    description
                                      "Layer on which encryption is applied.";
                                  }
                                  description
                                    "Container for CE-PE security encryption.";
                                }

                                container encryption-profile {
                                  choice profile {
                                    case provider-profile {
                                      leaf profile-name {
                                        type leafref {
                                          path "/l3vpn-ntw/vpn-profiles/" 
                                             + "valid-provider-identifiers"
                                             + "/encryption-profile-identifier/id";
                                        }
                                        description
                                          "Name of the SP profile to be applied.";
                                      }
                                    }
                                    case customer-profile {
                                      leaf algorithm {
                                        type string;
                                        description
                                          "Encryption algorithm to be used.";
                                      }
                                    }
                                    description
                                      "Choice for encryption profile.";
                                  }
                                  choice key-type {
                                    default "psk";
                                    case psk {
                                      leaf preshared-key {
                                        type string;
                                        description
                                          "Pre-Shared Key (PSK) coming from the customer.";
                                      }
                                    }
                                    description
                                      "Choice of encryption profile.
                                       The encryption profile can be the provider profile
                                       or customer profile.";
                                  }
                                  description
                                    "Container for encryption profile.";
                                }
                            description
                              "Site-specific security parameters.";
                          }

                      container routing-protocols {
                        list routing-protocol {
                          key "id";
                          leaf id {
                            type string;
                            description
                              "Unique identifier for routing protocol.";
                          }
                          leaf type {
                            type identityref {
                              base vpn-common:routing-protocol-type;
                            }
                            description
                              "Type of routing protocol.";
                          }
                          list routing-profiles {
                            key "id";
                            leaf id {
                              type leafref {
                                path "/l3vpn-ntw/vpn-profiles/" 
                                   + "valid-provider-identifiers"
                                   + "/routing-profile-identifier/id";
                              }
                              description
                                "Routing profile to be used.";
                            }
                            leaf type {
                              type identityref {
                                base vpn-common:ie-type;
                              }
                              description
                                "Import, export or both.";
                            }
                          }
                          container ospf {
                            when "derived-from-or-self(../type, 'vpn-common:ospf')" {
                              description
                                "Only applies when protocol is OSPF.";
                            }
                            if-feature "vpn-common:rtg-ospf";
                            leaf-list address-family {
                              type vpn-common:address-family;
                              min-elements 1;
                              description
                                "If OSPF is used on this site, this node
                                 contains a configured value.  This node
                                 contains at least one address family
                                 to be activated.";
                            }
                            leaf area-address {
                              type yang:dotted-quad;
                              mandatory true;
                              description
                                "Area address.";
                            }
                            leaf metric {
                              type uint16;
                              default "1";
                              description
                                "Metric of the PE-CE link.  It is used
                                 in the routing state calculation and
                                 path selection.";
                            }
                            leaf mtu {
                              type uint16;
                              description
                                "Maximum transmission unit for a given
                                 OSPF link.";
                            }
                            leaf process-id {
                              type uint16;
                              description
                                "Process id of the OSPF CE-PE connection.";
                            }
                            uses security-params;
                            container sham-links {
                              if-feature "vpn-common:rtg-ospf-sham-link";
                              list sham-link {
                                key "target-site";
                                leaf target-site {
                                  type vpn-common:svc-id;
                                  description
                                    "Target site for the sham link connection.
                                     The site is referred to by its ID.";
                                }
                                leaf metric {
                                  type uint16;
                                  default "1";
                                  description
                                    "Metric of the sham link.  It is used in
                                     the routing state calculation and path
                                     selection.  The default value is set
                                     to 1.";
                                }
                                description
                                  "Creates a sham link with another site.";
                              }
                              description
                                "List of sham links.";
                            }
                            description
                              "OSPF-specific configuration.";
                          }
                          container bgp {
                            when "derived-from-or-self(../type, 'vpn-common:bgp')" {
                              description
                                "Only applies when protocol is BGP.";
                            }
                            if-feature "vpn-common:rtg-bgp";
                            leaf peer-autonomous-system {
                              type inet:as-number;
                              mandatory true;
                              description
                                "Customer AS number in case the customer
                                 requests BGP routing.";
                            }
                            leaf local-autonomous-system {
                              type inet:as-number;
                              description
                                "Local-AS overwrite.";
                            }
                            leaf-list address-family {
                              type vpn-common:address-family;
                              min-elements 1;
                              description
                                "If BGP is used on this site, this node
                                 contains a configured value.  This node
                                 contains at least one address family
                                 to be activated.";
                            }
                            leaf-list neighbor {
                              type inet:ip-address;
                              description
                                "IP address(es) of the BGP neighbor. An IPv4
                                 and IPv6 neighbors may be indicated if
                                 two sessions will be used for IPv4 and IPv6.";
                            }
                            leaf multihop {
                              type uint8;
                              description
                                "Describes the number of hops allowed between 
                                 a given BGP neighbor and the PE router.";
                            }
                            uses security-params;
                            uses vpn-common:service-status;
                            leaf description {
                              type string;
                              description
                                "Includes a description of the BGP session.
                                 Such description is meant to be used for
                                 diagnosis purposes. The semantic of the description
                                 is local to an implementation.";
                            }
                            description
                              "BGP-specific configuration.";
                          }
                          container isis {
                            when "derived-from-or-self(../type, 'vpn-common:isis')" {
                              description
                                "Only applies when protocol is ISIS.";
                            }
                            if-feature "vpn-common:rtg-isis";
                            leaf-list address-family {
                              type vpn-common:address-family;
                              min-elements 1;
                              description
                                "If ISIS is used on this site, this node
                                 contains a configured value.  This node
                                 contains at least one address family
                                 to be activated.";
                            }
                            
                            leaf area-address {
                              type yang:dotted-quad;
                              mandatory true;
                              description
                                "Area address.";
                            }
                            
                            leaf level {
                              type identityref {
                                base vpn-common:isis-level;
                                }
                                description
                                  "level1, level2 or level1-2";
                              }

                            leaf metric {
                              type uint16;
                              default "1";
                              description
                                "Metric of the PE-CE link.  It is used
                                 in the routing state calculation and
                                 path selection.";
                            }
                            leaf process-id {
                              type uint16;
                              description
                                "Process id of the ISIS CE-PE connection.";
                            }
                            leaf mode {
                              type enumeration {
                                enum active {
                                  description
                                    "Interface sends or receives ISIS protocol
                                     control packets.";
                                }
                                enum passive {
                                  description
                                    "Suppresses the sending of ISIS routing updates 
                                     through the specified interface.";
                                }
                              }
                              default "active";
                              description
                                "ISIS interface mode type.";
                            }
                            uses vpn-common:service-status;
                            description
                              "ISIS-specific configuration.";
                          }
                          container static {
                            when "derived-from-or-self(../type, 'vpn-common:static')" {
                              description
                                "Only applies when protocol is static.
                                 BGP activation requires the SP to know
                                 the address of the customer peer.  When
                                 BGP is enabled, the 'static-address'
                                 allocation type for the IP connection
                                 MUST be used.";
                            }
                            container cascaded-lan-prefixes {
                              list ipv4-lan-prefixes {
                                if-feature "vpn-common:ipv4";
                                key "lan next-hop";
                                leaf lan {
                                  type inet:ipv4-prefix;
                                  description
                                    "LAN prefixes.";
                                }
                                leaf lan-tag {
                                  type string;
                                  description
                                    "Internal tag to be used in VPN policies.";
                                }
                                leaf next-hop {
                                  type inet:ipv4-address;
                                  description
                                    "Next-hop address to use on the customer side.";
                                }
                                description
                                  "List of LAN prefixes for the site.";
                              }
                              list ipv6-lan-prefixes {
                                if-feature "vpn-common:ipv6";
                                key "lan next-hop";
                                leaf lan {
                                  type inet:ipv6-prefix;
                                  description
                                    "LAN prefixes.";
                                }
                                leaf lan-tag {
                                  type string;
                                  description
                                    "Internal tag to be used in VPN policies.";
                                }
                                leaf next-hop {
                                  type inet:ipv6-address;
                                  description
                                    "Next-hop address to use on the customer side.";
                                }
                                description
                                  "List of LAN prefixes for the site.";
                              }
                              description
                                "LAN prefixes from the customer.";
                            }
                            description
                              "Configuration specific to static routing.";
                          }
                          container rip {
                            when "derived-from-or-self(../type, 'vpn-common:rip')" {
                              description
                                "Only applies when the protocol is RIP.  For IPv4,
                                 the model assumes that RIP version 2 is used.";
                            }
                            if-feature "vpn-common:rtg-rip";
                            leaf-list address-family {
                              type vpn-common:address-family;
                              min-elements 1;
                              description
                                "If RIP is used on this site, this node
                                 contains a configured value.  This node
                                 contains at least one address family
                                 to be activated.";
                            }
                            description
                              "Configuration specific to RIP routing.";
                          }
                          container vrrp {
                            when "derived-from-or-self(../type, 'vpn-common:vrrp')" {
                              description
                                "Only applies when protocol is VRRP.";
                            }
                            if-feature "vpn-common:rtg-vrrp";
                            leaf-list address-family {
                              type vpn-common:address-family;
                              min-elements 1;
                              description
                                "If VRRP is used on this site, this node
                                 contains a configured value.  This node contains
                                 at least one address family to be activated.";
                            }
                            description
                              "Configuration specific to VRRP routing.";
                          }
                          description
                            "List of routing protocols used on
                             the site.  This list can be augmented.";
                        }
                        description
                          "Defines routing protocols.";
                      }    

                      container service {
                         leaf svc-input-bandwidth {
                          type uint64;
                          units "bps";
                          mandatory true;
                          description
                            "From the customer site's perspective, the service
                             input bandwidth of the connection or download
                             bandwidth from the SP to the site.";
                        }
                        leaf svc-output-bandwidth {
                          type uint64;
                          units "bps";
                          mandatory true;
                          description
                            "From the customer site's perspective, the service
                             output bandwidth of the connection or upload
                             bandwidth from the site to the SP.";
                        }
                        leaf svc-mtu {
                          type uint16;
                          units "bytes";
                          mandatory true;
                          description
                            "MTU at service level.  If the service is IP,
                             it refers to the IP MTU.  If CsC is enabled,
                             the requested 'svc-mtu' leaf will refer to the
                             MPLS MTU and not to the IP MTU.";
                        }

                        container qos {
                              if-feature "vpn-common:qos";
                              container qos-classification-policy {
                                list rule {
                                  key "id";
                                  ordered-by user;
                                  leaf id {
                                    type string;
                                    description
                                      "A description identifying the
                                       qos-classification-policy rule.";
                                  }
                                  choice match-type {
                                    default "match-flow";
                                    case match-flow {
                                      choice l3 {
                                        container ipv4 {
                                          uses packet-fields:acl-ip-header-fields;
                                          uses packet-fields:acl-ipv4-header-fields;
                                          description
                                            "Rule set that matches IPv4 header.";
                                        }
                                        container ipv6 {
                                          uses packet-fields:acl-ip-header-fields;
                                          uses packet-fields:acl-ipv6-header-fields;
                                          description
                                            "Rule set that matches IPv6 header.";
                                        }
                                        description
                                          "Either IPv4 or IPv6.";
                                      }
                                      choice l4 {
                                        container tcp {
                                          uses packet-fields:acl-tcp-header-fields;
                                          uses ports;
                                          description
                                            "Rule set that matches TCP header.";
                                        }
                                        container udp {
                                          uses packet-fields:acl-udp-header-fields;
                                          uses ports;
                                          description
                                            "Rule set that matches UDP header.";
                                        }
                                        description
                                          "Can be TCP or UDP";
                                      }
                                    }
                                    case match-application {
                                      leaf match-application {
                                        type identityref {
                                          base vpn-common:customer-application;
                                        }
                                        description
                                          "Defines the application to match.";
                                      }
                                    }
                                    description
                                      "Choice for classification.";
                                  }
                                  leaf target-class-id {
                                    type string;
                                    description
                                      "Identification of the class of service.
                                       This identifier is internal to the administration.";
                                  }
                                  description
                                    "List of marking rules.";
                                }
                                description
                                  "Configuration of the traffic classification policy.";
                              }
                              container qos-profile {
                                list qos-profile {
                                  key profile;
                                  description
                                    "QoS profile.
                                     Can be standard profile or customized profile.";
                                    leaf profile {
                                      type leafref {
                                        path "/l3vpn-ntw/vpn-profiles/" 
                                           + "valid-provider-identifiers"
                                           + "/qos-profile-identifier/id";
                                      }
                                      description
                                        "QoS profile to be used.";
                                    }
                                    leaf direction {
                                      type identityref {
                                        base vpn-common:qos-profile-direction;
                                      }
                                      default "vpn-common:both";
                                      description
                                        "The direction to which the QoS profile
                                         is applied.";
                                    }
                                }
                                description
                                  "QoS profile configuration.";
                              }
                              description
                                "QoS configuration.";
                            }

                        container carrierscarrier {
                            if-feature "vpn-common:carrierscarrier";
                            leaf signalling-type {
                              type enumeration {
                                enum ldp {
                                  description
                                    "Use LDP as the signalling protocol
                                     between the PE and the CE.  In this case,
                                     an IGP routing protocol must also be activated.";
                                }
                                enum bgp {
                                  description
                                    "Use BGP as the signalling protocol
                                     between the PE and the CE.
                                     In this case, BGP must also be configured as
                                     the routing protocol.";
                                  reference
                                    "RFC 8277: Using BGP to Bind MPLS Labels to 
                                               Address Prefixes";
                                }
                              }
                              default "bgp";
                              description
                                "MPLS signalling type.";
                            }
                            description
                              "This container is used when the customer provides
                               MPLS-based services.  This is only used in the case
                               of CsC (i.e., a customer builds an MPLS service using
                               an IP VPN to carry its traffic).";
                          }

                          container multicast {
                                if-feature "vpn-common:multicast";
                                leaf site-type {
                                  type enumeration {
                                    enum receiver-only {
                                      description
                                        "The site only has receivers.";
                                    }
                                    enum source-only {
                                      description
                                        "The site only has sources.";
                                    }
                                    enum source-receiver {
                                      description
                                        "The site has both sources and receivers.";
                                    }
                                  }
                                  default "source-receiver";
                                  description
                                    "Type of multicast site.";
                                }
                                leaf address-family {
                                  type vpn-common:address-family;
                                  }

                                leaf protocol-type {
                                  type enumeration {
                                    enum host {
                                      description
                                        "Hosts are directly connected to the provider network.
                                         Host protocols such as IGMP or MLD are required.";
                                    }
                                    enum router {
                                      description
                                        "Hosts are behind a customer router.
                                         PIM will be implemented.";
                                    }
                                    enum both {
                                      description
                                        "Some hosts are behind a customer router, and
                                         some others are directly connected to the
                                         provider network.  Both host and routing protocols
                                         must be used.  Typically, IGMP and PIM will be
                                         implemented.";
                                    }
                                  }
                                  default "both";
                                  description
                                    "Multicast protocol type to be used with the customer site.";
                                }
                                leaf remote-source {
                                  type boolean;
                                  default "false";
                                  description
                                    "When true, there is no PIM adjacency on the interface.";
                                }
                                description
                                  "Multicast parameters for the site.";
                              }


                        description
                          "Service parameters on the attachment.";
                      }
                      description
                        "List of accesses for a site.";
                    }
                    description
                      "List of accesses for a site.";
                  }
                  

                  container maximum-routes {
                    list address-family {
                      key "af";
                      leaf af {
                        type vpn-common:address-family;
                        description
                          "Address family.";
                      }
                      leaf maximum-routes {
                        type uint32;
                        description
                          "Maximum prefixes the VRF can accept
                           for this address family.";
                      }
                      description
                        "List of address families.";
                    }
                    description
                      "Defines 'maximum-routes' for the VRF.";
                  }
                  
                  container multicast {
                    if-feature "vpn-common:multicast";
                    leaf enabled {
                      type boolean;
                      default "false";
                      description
                        "Enables multicast.";
                    }
                    leaf-list tree-flavor {
                      type identityref {
                        base vpn-common:multicast-tree-type;
                      }
                      description
                        "Type of tree to be used.";
                    }
                    container rp {
                      container rp-group-mappings {
                        list rp-group-mapping {
                          key "id";
                          leaf id {
                            type uint16;
                            description
                              "Unique identifier for the mapping.";
                          }
                          container provider-managed {
                            leaf enabled {
                              type boolean;
                              default "false";
                              description
                                "Set to true if the Rendezvous Point (RP)
                                 must be a provider-managed node.  Set to false
                                 if it is a customer-managed node.";
                            }
                            leaf rp-redundancy {
                              type boolean;
                              default "false";
                              description
                                "If true, a redundancy mechanism for the RP
                                 is required.";
                            }
                            leaf optimal-traffic-delivery {
                              type boolean;
                              default "false";
                              description
                                "If true, the SP must ensure that
                                 traffic uses an optimal path.  An SP may use
                                 Anycast RP or RP-tree-to-SPT switchover
                                 architectures.";
                            }
                            container anycast {
                              when "../rp-redundancy = 'true' and
                                    ../optimal-traffic-delivery = 'true'" {
                                  description
                                    "Only applicable if
                                     RP redundancy is
                                     enabled and delivery through
                                     optimal path is activated.";
                              }
                              leaf local-address {
                                type inet:ip-address;
                                description
                                  "IP local address for PIM RP.
                                   Usually, it corresponds to router
                                   ID or primary address";
                              }
                              leaf-list rp-set-address {
                                type inet:ip-address;
                                description
                                  "Address other RP routers
                                   that share the same RP IP address.";
                              }
                              description
                                "PIM Anycast-RP parameters.";
                            }
                            description
                              "Parameters for a provider-managed RP.";
                          }
                          leaf rp-address {
                            when "../provider-managed/enabled = 'false'" {
                              description
                                "Relevant when the RP is not provider-managed.";
                            }
                            type inet:ip-address;
                            mandatory true;
                            description
                              "Defines the address of the RP.
                               Used if the RP is customer-managed.";
                          }
                          container groups {
                            list group {
                              key "id";
                              leaf id {
                                type uint16;
                                description
                                  "Identifier for the group.";
                              }
                                  choice group-format {
                                    mandatory true;
                                    case group-prefix {
                                      leaf group-address {
                                        type inet:ip-prefix;
                                        description
                                          "A single multicast group prefix.";
                                      }
                                    }
                                    case startend {
                                      leaf group-start {
                                        type inet:ip-address;
                                        description
                                          "The first multicast group address in
                                           the multicast group address range.";
                                      }
                                      leaf group-end {
                                        type inet:ip-address;
                                        description
                                          "The last multicast group address in
                                           the multicast group address range.";
                                      }
                                    }
                                    description
                                      "Choice for multicast group format.";
                                  }
                              description
                                "List of multicast groups.";
                            }
                            description
                              "Multicast groups associated with the RP.";
                          }
                          description
                            "List of RP-to-group mappings.";
                        }
                        description
                          "RP-to-group mappings parameters.";
                      }
                      container rp-discovery {
                        leaf rp-discovery-type {
                          type identityref {
                            base vpn-common:multicast-rp-discovery-type;
                          }
                          default "vpn-common:static-rp";
                          description
                            "Type of RP discovery used.";
                        }
                        container bsr-candidates {
                          when "derived-from-or-self(../rp-discovery-type, "
                             + "'vpn-common:bsr-rp')" {
                            description
                              "Only applicable if discovery type
                               is BSR-RP.";
                          }
                          leaf-list bsr-candidate-address {
                            type inet:ip-address;
                            description
                              "Address of candidate Bootstrap Router (BSR).";
                          }
                          description
                            "Container for List of Customer
                             BSR candidate's addresses.";
                        }
                        description
                          "RP discovery parameters.";
                      }
                      description
                        "RP parameters.";
                    }
                    container msdp {
                      if-feature "msdp";
                      leaf enabled {
                        type boolean;
                        default "false";
                        description
                          "If true, Multicast Source Discovery Protocol (MSDP) protocol is activated.";
                      }
                      leaf peer {
                        type inet:ip-address;
                        description
                          "IP address of the MSDP peer.";
                      }
                      leaf local-address {
                        type inet:ip-address;
                        description
                          "IP address of the local end. This local address must be configured on the node.";
                      }
                      description
                        "MSDP parameters.";
                    }
                    description
                      "Multicast global parameters for the VPN service.";
                  }

                  description
                    "List for VPN node.";
                }
          }
        description
          "List of VPN services.";
      }
      description
        "Top-level container for the VPN services.";
    }
    description
      "Main container for L3VPN services management.";
  }
}
