module ietf-vpn-types {
  
  yang-version 1.1;
  namespace "urn:ietf:params:xml:ns:yang:ietf-vpn-types";
  prefix vpn-types;

  import ietf-netconf-acm {
    prefix nacm;
    reference
      "RFC 8341: Network Configuration Access Control Model";
  }

  import ietf-yang-types {
    prefix yang;
    reference
      "Section 3 of RFC 6991";
  }
  organization
    "IETF OPSA (Operations and Management Area) Working Group ";
  contact
    "WG Web:   <http://tools.ietf.org/wg/opsawg/>
        WG List:  <mailto:opsawg@ietf.org>
        Author:    Samier Barguil
                  <mailto:samier.barguilgiraldo.ext@telefonica.com>
        Editor:    Oscar Gonzalez de Dios
                  <mailto:oscar.gonzalezdedios@telefonica.com>
        Author:   Mohamed Boucadair
                  <mailto:mohamed.boucadair@orange.com>           
        Author:    Luis Angel Munoz
                  <mailto:luis-angel.munoz@vodafone.com>
        Author:    Alejandro Aguado
                  <mailto:alejandro.aguado_martin@nokia.com> 
    ";
  description
    "This YANG module defines a generic network-oriented model
     for the configuration of Layer 3 Virtual Private Networks.
     Copyright (c) 2020 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2020-06-03 {
    description
      "Initial revision.";
    reference
      "RFC XXXX: A VPN common types YANG Model";
      // RFC Ed.: replace XXXX with actual RFC number and remove
     // this note
  }

/* Feature */

 feature cloud-access {
  description
  "Allows the VPN to connect to a CSP.";
 }

/* Typedef */

/* Identities */

  identity operational-status {
        description
        "Base identity for Protocol Type.";
  }

  identity operational-state-up {
      base operational-status;
          description
            "Operational status UP/Enabled.";
        }

  identity operational-state-down {
      base operational-status;
          description
            "Operational status DOWN/Disabled.";
        }

  identity operational-state-unknown {
      base operational-status;
          description
            "Operational status UNKNOWN.";
        }


identity administrative-status {
        description
        "Base identity for Protocol Type.";
  }

  identity administrative-state-up {
      base administrative-status;
          description
            "Administrative status UP/Enabled.";
        }

  identity administrative-state-down {
      base administrative-status;
          description
            "Administrative status DOWN/Disabled.";
        }

  identity administrative-state-testing {
      base administrative-status;
          description
            "Administrative status UNKNOWN.";
        }


  identity encapsulation-type {
      description
      "Base identity for Protocol Type.";
  }

  identity priority-tagged {
    base encapsulation-type;
    description
      "Identity for the priority-tagged interface.";
  }

  identity dot1q {
  	base encapsulation-type;
    description
      "This identity indicates the support of
       the 'dot1q' encapsulation.";
  }

  identity qinq {
  	base encapsulation-type;
    description
      "This identity indicates the support of
       the 'qinq' encapsulation.";
  }

  identity qinany {
  	base encapsulation-type;
    description
      "This identity indicates the support of
       the 'qinany' encapsulation.";
  }

  identity vxlan {
  	base encapsulation-type;
    description
      "This identity indicates the support of
       the 'vxlan' encapsulation.";
  }

  identity tag-type {
    description
      "Base identity from which all tag types are derived.";
  }

  identity c-vlan {
    base tag-type;
    description
      "A CVLAN tag, normally using the 0x8100 Ethertype.";
  }

  identity s-vlan {
    base tag-type;
    description
      "An SVLAN tag.";
  }

  identity c-s-vlan {
    base tag-type;
    description
      "Using both a CVLAN tag and an SVLAN tag.";
  }

identity protocol-type {
      description
      "Base identity for Protocol Type.";
  }

  identity gre {
    base protocol-type ;
    description
         "GRE encapsulation.";
       reference
         "RFC 1701: Generic Routing Encapsulation (GRE)
          RFC 1702: Generic Routing Encapsulation over IPv4 networks
          RFC 7676: IPv6 Support for Generic Routing Encapsulation
                    (GRE)";
  }

  identity ldp {
    base protocol-type ;
    description
      "Transport based on LDP.";
      reference
        "";
  }
  
  identity bgp {
    base protocol-type ;
    description
      "Transport based on BGP.";
      reference
        "";
  }

  identity sr {
    base protocol-type ;
    description
      "Transport based on SR.";
      reference
        "";
  }

  identity sr-te {
    base protocol-type ;
    description
      "Transport based on SR-TE.";
      reference
        "";
  }

  identity rsvp-te {
    base protocol-type ;
    description
      "Transport based on RSVP-TE.";
      reference
        "";
  }

  identity unknown {
    base protocol-type ;
    description
      "Not known at this stage.";
      reference
        "";
  }

identity vpn-topology {
    description
      "Base identity for VPN topology.";
  }

  identity any-to-any {
    base vpn-topology;
    description
      "Identity for any-to-any VPN topology.";
  }

  identity hub-spoke {
    base vpn-topology;
    description
      "Identity for Hub-and-Spoke VPN topology.";
  }

  identity hub-spoke-disjoint {
    base vpn-topology;
    description
      "Identity for Hub-and-Spoke VPN topology
       where Hubs cannot communicate with each other.";
  }

  identity custom {
    base vpn-topology;
    description
      "Identity for CUSTOM VPN topology
       where Hubs can act as Spoke for certain part of
       the network or Spokes as Hubs.";
  }

/* Grouping */

grouping vpn-profile-cfg {
    container valid-provider-identifiers {
      list cloud-identifier {
        if-feature "cloud-access";
        key "id";
        leaf id {
          type string;
          description
            "Identification of cloud service.
             Local administration meaning.";
        }
        description
          "List for Cloud Identifiers.";
      }
      list encryption-profile-identifier {
        key "id";
        leaf id {
          type string;
          description
            "Identification of the SP encryption profile
             to be used.  Local administration meaning.";
        }
        description
          "List for encryption profile identifiers.";
      }
      list qos-profile-identifier {
        key "id";
        leaf id {
          type string;
          description
            "Identification of the QoS Profile to be used.
             Local administration meaning.";
        }
        description
          "List for QoS Profile Identifiers.";
      }
      list bfd-profile-identifier {
        key "id";
        leaf id {
          type string;
          description
            "Identification of the SP BFD Profile to be used.
             Local administration meaning.";
        }
        description
          "List for BFD Profile identifiers.";
      }
      list routing-profile-identifier {
        key "id";
        leaf id {
          type string;
          description
            "Identification of the routing Profile to be used
             by the routing-protocols within sites, vpn-
             network-accesses or vpn-nodes for refering
			 vrf-import/export policies.
             This identifier has a local meaning.";
        }
        description
          "List for Routing Profile Identifiers.";
      }
      nacm:default-deny-write;
      description
        "Container for Valid Provider Identifies.";
    }
    description
      "Grouping for VPN Profile configuration.";
  }

  grouping status-timestamp {
    leaf status {
      type identityref {
        base operational-status;
      }
      description
        "Operations status";
    }
    leaf timestamp {
      type yang:date-and-time;
      description
        "Indicates the actual date and time when
         the service actually started (UP) or
         stopped (DOWN).";
    }
    description
      "This grouping defines some operational
       parameters for the service.";
  }

  grouping service-status {
    container status {
      leaf admin-status {
        type identityref {
          base administrative-status;
        }
        description
          "Administrative service status.";
      }
      container oper-status {
        config false;
        uses status-timestamp;
        description
          "Operational service status.";
      }
      description
        "Service status.";
    }
    description
      "Service status grouping. Reused in
       vpn-node and vpn-network-access.";
  }


}
